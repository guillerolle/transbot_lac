# transbot

# Specification: Requirements Document
- ReqIF.Description: Stakeholder Requirements Specification (StRS)
- ReqIF.Name: Stakeholder Requirements Specification (StRS)

## SEC-2 (Section)
1 Introduction

### SEC-3 (Section)
1.1 Stakeholder Purpose

#### REQ-13 (Requirement Type)
Productivity
Stakeholder goal is to increase overall productivity

#### REQ-14 (Requirement Type)
Material Fetching Delays
Reduce the time that a production worker destines to material fetching activities

### SEC-14 (Section)
3 System Operational Requirements

#### SEC-15 (Section)
3.5 System Operational Quality
Define the level of quality required for the system operation, such as performance, compatibility, reliability, security, maintainability and portability. For example, a process can address required urgency with higher priority than the reliability of the process.

##### SEC-16 (Section)
3.5.1 Safety Requirements

###### REQ-21 (Requirement Type)
Human Safety
The system shall ensure the safety of human operators
- Priority: Critical
- VerMethod: Analysis
- VerStatus: Not Tested
- SpecRelation Type -> REQ-22
- SpecRelation Type -> REQ-23
- SpecRelation Type -> REQ-24
- SpecRelation Type -> REQ-25
- SpecRelation Type -> REQ-26
- SpecRelation Type -> REQ-27

#### REQ-28 (Requirement Type)
Ergonomy
The system shall be ergonomic for the operators

### SEC-4 (Section)
4 User Requirements

# Specification
- ReqIF.Description: System Requirements Specification (SyRS)
- ReqIF.Name: System Requirements Specification (SyRS)

## SEC-5 (Section)
1 Introduction

### SEC-6 (Section)
1.1 System purpose

#### REQ-17 (Requirement Type)
Mission
System's mission is to transport materials inside the factory

## SEC-7 (Section)
2 System Requirements

### SEC-8 (Section)
2.1 Functional Requirements
Define functional requirements applicable to system operation

#### REQ-22 (Requirement Type)
Avoid collisiions
The system shall avoid collisions with human beings

#### REQ-24 (Requirement Type)
Detect obstacles
The system shall detect obstacles

### SEC-12 (Section)
2.2 Usability Requirements
Define usability and quality in use requirements and objectives for the system that can include measurable effectiveness, efficiency, satisfaction criteria and avoidance of harm that could arise from use in specific contexts of use.

### SEC-10 (Section)
2.3 Performance Requirements
Define critical performance conditions and their associated capabilities by including such considerations as:
a) dynamic actions or changes that occur (e.g. rates, velocities, movements and noise levels) 
b) quantitative criteria covering endurance capabilities of the equipment required to meet the user needs under stipulated environmental and other conditions, including minimum total life expectancy. Indicate required operational session duration and planned utilization rate;
c) performance requirements for the operational phases and modes

#### REQ-19 (Requirement Type)
No-load navigation cycle time
System shall make a "no-load" work cycle around the factory in under 2 minutes

#### REQ-20 (Requirement Type)
Loaded navigation cycle time
System shall make a "loaded" work cycle around the factory in under 5 minutes

#### REQ-23 (Requirement Type)
Travel speed
The system travel speed shall be limited to <= 3km/h in human-occupied zones

#### REQ-25 (Requirement Type)
Bumper emergency
The system shall, upon bumper compression, engage emergency brakes within 50 ms

#### REQ-31 (Requirement Type)
Material Integrity under Transport Dynamics
The system shall transport the material such that the materials remains within its designated payload zone and suffers no physical damage during maneuvers
- VerMethod: Test

### SEC-13 (Section)
2.4 System interface requirements
Specify requirements for interfaces that among system elements and with external entities. Interfaces among system elements should include interfaces with the human element. Interfaces with external entities should include other systems.

Define any interdependencies or constraints associated with the interfaces (e.g., communication protocols, special devices, standards, fixed formats). Each interface may represent a bidirectional flow of information. A graphic representation of the interfaces can be used when appropiate for the sake of clarity

#### REQ-29 (Requirement Type)
Request interface
The system shall provide the working operator with an interface to request materials replenishment

### SEC-17 (Section)
2.5 System Operations

#### SEC-18 (Section)
2.5.4 Other Quality Requirements

##### REQ-26 (Requirement Type)
Minimizing injury design
The system shall be designed to minimize injury upon collision

### SEC-19 (Section)
2.7 Physical Characteristics

#### SEC-20 (Section)
2.7.1 Physical Requirements

##### REQ-27 (Requirement Type)
Rounded profile
The chassis shall have a rounded profile with no sharp edges
